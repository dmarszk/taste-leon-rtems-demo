TASTE-Dataview DEFINITIONS ::=
BEGIN
IMPORTS T-Int32, T-UInt32, T-Int8, T-UInt8, T-Boolean FROM TASTE-BasicTypes;

UART-String    ::= OCTET STRING (SIZE (384))

GPS-Status      ::= ENUMERATED { offline, no-position-fix, valid-position-fix } 

LEON-UART-Configuration ::= SEQUENCE {
	console-id INTEGER(0..9),
	baud INTEGER(0..921600)
}

CAN-Frame ::= SEQUENCE {
	id T-UInt32, -- 11 or 29 bit identifier 
	len T-UInt8,
	data OCTET STRING (SIZE (8))
}

END
